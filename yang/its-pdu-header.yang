module its-pdu-header {
    namespace "urn:example:params:xml:ns:yang:its-pdu-header";
    prefix "itsPduHeader";

    typedef OrdinalNumber1B {
        type uint8 {
            range "0..255";
        }
        description
          "An ordinal number ranging from 0 to 255. Explicit range necessary?";
    }

    typedef StationId {
        type uint32{
            range "0..4294967295";
        }
        description
          "A station identity ranging from 0 to 2^32";
    }

    typedef MessageId {
        type union {
            type uint8{
                range "0..255";
            }
            type enumeration {
                enum denm {
                    value 1;
                    description
                      "Decentralized Environmental Notification Message";
                }
                enum cam {
                    value 2;
                }
                enum poim {
                    value 3;
                }
                enum spatem {
                    value 4;
                }
                enum mapem {
                    value 5;
                }
                enum ivim {
                    value 6;
                }
                enum rfu1 {
                    value 7;
                }
                enum rfu2 {
                    value 8;
                }
                enum srem {
                    value 9;
                }
                enum ssem {
                    value 10;
                }
                enum evcsn {
                    value 11;
                }
                enum saem {
                    value 12;
                }
                enum rtcmem {
                    value 13;
                }
                enum cpm {
                    value 14;
                }
                enum imzm {
                    value 15;
                }
                enum vam {
                    value 16;
                }
                enum dsm {
                    value 17;
                }
                enum pcim {
                    value 18;
                }
                enum pcvm {
                    value 19;
                }
                enum mcm {
                    value 20;
                }
                enum pam {
                    value 21;
                }
            }
        }
    }

    grouping its-pdu-header {
        description
          "Container for ITS PDU Header";
        leaf protocolVersion {
            type OrdinalNumber1B;
            description
              "Protocol version ranging from 0 to 255";
        }

        leaf messageID {
            type MessageId;
        }

        leaf stationID {
            type StationId;
        }
    }
}
